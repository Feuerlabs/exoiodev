/*
 *  Model of analog value reporting
 * 
 *  Notification support:
 *
 *  A analog value is notified:
 *  if upper-limit-exceeded  AND  (calc-value > upper-limit)
 *  if below-lower-limit     AND  (calc-value < lower-limit)
 *  if changed-by-more-than-delta AND abs(calc-value-calc-value') > delta
 *  if changed-by-more-than-negative-delta AND (calc-value < calc-value') AND
 *              (calc-value' - calc-value) > neg-delta
 *  if changed-by-more-than-positive-delta AND (calc-value > calc-value') AND
 *              (calc-value - calc-value') > pos-delta
 *
 *  calc-value' is the previos value on calc-value
 * 
 *  FIXME: add configurable filtering support, mean value calculation
 *         spike filtering support, interval etc.
 */
module exo-analog {
    namespace "http://feuerlabs.com/ns/exo-analog";
    prefix "adc";

    organization
	"FeuerLabs Inc";

    contact 
	"Tony Rogvall <tony@feuerlabs.com>";

    description "Analog input module";

    typedef trigger-type {
    	type union {
	    type uint8;
	    type bits {
		bit upper-limit-exceeded { 
		    position 0; 
		}
		bit below-lower-limit {
		    position 1;
		}
		bit changed-by-more-than-delta {
		    position 2;
		}
		bit changed-by-more-than-negative-delta {
		    position 3;
		}
		bit changed-by-more-than-positive-delta {
		    position 4;
		}
	    }
	}
    }
    
    grouping analog-16 {

	description "Analog value settings.
                     The analog value is streamed when the trigger-selection
                     is fulfilled.";

	leaf index {
	    type int32;
	    mandatory true;
	    description "The ADC number used";
	}

	leaf name {
	    type string;
	    description "The name label used";
	}

	leaf trigger-selection {
	    type adc:trigger-type;
	    description "select notification trigger";
	}

	leaf scale {
	    type int32;
	    default 1;
	}

	leaf offset {
	    type int32;
	    default 0;
	}

	leaf value {
	    type uint16;
	    config false;
	    // event-stream true;  could be a way of declaring event streams
	    description "The analog value in full range, note that if
                         10 bit analog values are used, they must be
                         scaled to 16 bit by, for example, a shift operation.";
	}

	leaf scaled-value {
	    type int32;
	    config false;
	    description "The last scaled value: value*scale + offset";
	}

	leaf upper-limit {
	    type int32;
	    description "Upper limit for trigger selection on calc-value";
	}

	leaf lower-limit {
	    type int32;
	    description "Lower limit for trigger selection on calc-value";
	}

	leaf delta {
	    description "Delta value used in change-by-more-than-delta";
	    type uint32;
	}

	leaf negative-delta {
	    description "Delta value used in 
                         change-by-more-than-negative-delta";
	    type uint32;
	}

	leaf positive-delta {
	    description "Delta value used in 
                         change-by-more-than-positive-delta";
	    type uint32;
	}

	leaf sample-frequency {
	    description "Frequency to sample analog values";
	    type decimal64 {
		fraction-digits 2;
	    }
	}

	leaf max-transmit-frequency {
	    description "Maximum frequence to latch triggered samples, this
                         defines an inhibit time period of 1/F. It is specified
                         in Hz, number of samples per second";
	    type decimal64 {
		fraction-digits 2;
	    }
	}
    }
}
